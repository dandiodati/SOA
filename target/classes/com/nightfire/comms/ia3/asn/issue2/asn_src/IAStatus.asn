-- Copyright(c) 2000 NightFire Software, Inc.
-- All rights reserved

Issue2-IAStatus

DEFINITIONS EXPLICIT TAGS ::=
BEGIN

eciaAscX12Edi OBJECT IDENTIFIER ::= {
    iso(1) org(3) dod(6) internet(1) private(4) enterprises(1)
    mciwcom(3576) 7
}

IAStatus ::= SEQUENCE {
    iaStatusMessage OBJECT IDENTIFIER,
    iaStatus [0] EXPLICIT BIT STRING -- ( SIZE(32) )
}

-- The first OID gets an extra 0 prepended for some reason
bogusOID OBJECT IDENTIFIER ::= { eciaAscX12Edi 99 }

plainEDImessage OBJECT IDENTIFIER ::= { eciaAscX12Edi 1 }
iaReceiptMessage OBJECT IDENTIFIER ::= { eciaAscX12Edi 65 }
iaStatusMessage OBJECT IDENTIFIER ::= { eciaAscX12Edi 97 }

END
